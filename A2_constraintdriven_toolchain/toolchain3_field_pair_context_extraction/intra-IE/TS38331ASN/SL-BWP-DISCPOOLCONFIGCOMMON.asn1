SL-BWP-DiscPoolConfigCommon-r17 ::= SEQUENCE {
    sl-DiscRxPool-r17                   SEQUENCE (SIZE (1..maxNrofRXPool-r16)) OF SL-ResourcePool-r16         OPTIONAL,    -- Need R
    sl-DiscTxPoolSelected-r17           SEQUENCE (SIZE (1..maxNrofTXPool-r16)) OF SL-ResourcePoolConfig-r16   OPTIONAL,    -- Need R
    ...
}
