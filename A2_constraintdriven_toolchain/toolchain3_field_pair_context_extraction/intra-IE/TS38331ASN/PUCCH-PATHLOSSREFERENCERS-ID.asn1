PUCCH-PathlossReferenceRS-Id ::=            INTEGER (0..maxNrofPUCCH-PathlossReferenceRSs-1)

PUCCH-PathlossReferenceRS-Id-v1610 ::=      INTEGER (maxNrofPUCCH-PathlossReferenceRSs..maxNrofPUCCH-PathlossReferenceRSs-1-r16)

PUCCH-PathlossReferenceRS-Id-r17 ::=        INTEGER (0..maxNrofPUCCH-PathlossReferenceRSs-1-r17)
