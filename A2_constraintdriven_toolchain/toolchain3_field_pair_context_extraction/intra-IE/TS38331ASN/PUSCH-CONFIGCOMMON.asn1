PUSCH-ConfigCommon ::=                  SEQUENCE {
    groupHoppingEnabledTransformPrecoding   ENUMERATED {enabled}                                                OPTIONAL,   -- Need R
    pusch-TimeDomainAllocationList          PUSCH-TimeDomainResourceAllocationList                              OPTIONAL,   -- Need R
    msg3-DeltaPreamble                      INTEGER (-1..6)                                                     OPTIONAL,   -- Need R
    p0-NominalWithGrant                     INTEGER (-202..24)                                                  OPTIONAL,   -- Need R
    ...
}
