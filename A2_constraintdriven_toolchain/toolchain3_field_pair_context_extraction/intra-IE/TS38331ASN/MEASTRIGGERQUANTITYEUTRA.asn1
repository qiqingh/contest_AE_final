MeasTriggerQuantityEUTRA::=                 CHOICE {
    rsrp                                        RSRP-RangeEUTRA,
    rsrq                                        RSRQ-RangeEUTRA,
    sinr                                        SINR-RangeEUTRA
}

RSRP-RangeEUTRA ::=                 INTEGER (0..97)

RSRQ-RangeEUTRA ::=                 INTEGER (0..34)

SINR-RangeEUTRA ::=                 INTEGER (0..127)
