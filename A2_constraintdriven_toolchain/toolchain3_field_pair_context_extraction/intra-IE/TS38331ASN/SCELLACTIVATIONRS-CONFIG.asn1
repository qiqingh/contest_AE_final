SCellActivationRS-Config-r17 ::= SEQUENCE {
    scellActivationRS-Id-r17         SCellActivationRS-ConfigId-r17,
    resourceSet-r17                  NZP-CSI-RS-ResourceSetId,
    gapBetweenBursts-r17             INTEGER (2..31)                                                            OPTIONAL, -- Need R
    qcl-Info-r17                     TCI-StateId,
    ...
}
