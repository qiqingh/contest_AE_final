VarMeasConfigSL-r16 ::=                        SEQUENCE {
    -- NR sidelink measurement identities
    sl-MeasIdList-r16                              SL-MeasIdList-r16                          OPTIONAL,
    -- NR sidelink measurement objects
    sl-MeasObjectList-r16                          SL-MeasObjectList-r16                      OPTIONAL,
    -- NR sidelink reporting configurations
    sl-reportConfigList-r16                        SL-ReportConfigList-r16                    OPTIONAL,
    -- Other parameters
    sl-QuantityConfig-r16                          SL-QuantityConfig-r16                      OPTIONAL
}
