SL-RLC-BearerConfig-r16 ::=                   SEQUENCE {
    sl-RLC-BearerConfigIndex-r16                  SL-RLC-BearerConfigIndex-r16,
    sl-ServedRadioBearer-r16                      SLRB-Uu-ConfigIndex-r16                          OPTIONAL,   -- Cond LCH-SetupOnly
    sl-RLC-Config-r16                             SL-RLC-Config-r16                                OPTIONAL,   -- Cond LCH-Setup
    sl-MAC-LogicalChannelConfig-r16               SL-LogicalChannelConfig-r16                      OPTIONAL,   -- Cond LCH-Setup
    ...
}
