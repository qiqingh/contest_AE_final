ZP-CSI-RS-ResourceSet ::=           SEQUENCE {
    zp-CSI-RS-ResourceSetId             ZP-CSI-RS-ResourceSetId,
    zp-CSI-RS-ResourceIdList            SEQUENCE (SIZE(1..maxNrofZP-CSI-RS-ResourcesPerSet)) OF ZP-CSI-RS-ResourceId,
    ...
}
