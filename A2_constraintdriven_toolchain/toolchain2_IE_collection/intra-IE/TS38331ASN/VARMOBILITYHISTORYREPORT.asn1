VarMobilityHistoryReport-r16 ::= VisitedCellInfoList-r16

VarMobilityHistoryReport-r17 ::= SEQUENCE {
    visitedCellInfoList-r16          VisitedCellInfoList-r16,
    visitedPSCellInfoListReport-r17  VisitedPSCellInfoList-r17         OPTIONAL
}
