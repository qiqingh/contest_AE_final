VarRA-Report-r16 ::=      SEQUENCE {
    ra-ReportList-r16         RA-ReportList-r16,
    plmn-IdentityList-r16     PLMN-IdentityList-r16
}

PLMN-IdentityList-r16 ::= SEQUENCE (SIZE (1..maxPLMN)) OF PLMN-Identity
