SDAP-Parameters ::= SEQUENCE {
    as-ReflectiveQoS                 ENUMERATED {true}               OPTIONAL,
    ...,
    [[
    sdap-QOS-IAB-r16              ENUMERATED {supported}       OPTIONAL,
    sdapHeaderIAB-r16             ENUMERATED {supported}       OPTIONAL
    ]]

}
