SL-BWP-ConfigCommon-r16 ::=              SEQUENCE {
    sl-BWP-Generic-r16                       SL-BWP-Generic-r16                                         OPTIONAL,    -- Need R
    sl-BWP-PoolConfigCommon-r16              SL-BWP-PoolConfigCommon-r16                                OPTIONAL,    -- Need R
    ...,
    [[
    sl-BWP-PoolConfigCommonPS-r17            SL-BWP-PoolConfigCommon-r16                                OPTIONAL,    -- Need R
    sl-BWP-DiscPoolConfigCommon-r17          SL-BWP-DiscPoolConfigCommon-r17                            OPTIONAL     -- Need R
    ]]
}
