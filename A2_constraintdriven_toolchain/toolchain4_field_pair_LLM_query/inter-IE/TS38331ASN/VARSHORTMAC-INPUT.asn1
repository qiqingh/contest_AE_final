VarShortMAC-Input   ::=                 SEQUENCE {
    sourcePhysCellId                        PhysCellId,
    targetCellIdentity                      CellIdentity,
    source-c-RNTI                           RNTI-Value
}
