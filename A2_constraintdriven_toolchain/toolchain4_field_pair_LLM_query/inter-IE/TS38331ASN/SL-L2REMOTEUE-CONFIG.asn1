SL-L2RemoteUE-Config-r17 ::=      SEQUENCE {
    sl-SRAP-ConfigRemote-r17          SL-SRAP-Config-r17                                    OPTIONAL,  --Need M
    sl-UEIdentityRemote-r17           RNTI-Value                                            OPTIONAL, -- Cond FirstRRCReconfig
    ...
}
