LocationInfo-r16 ::=      SEQUENCE {
    commonLocationInfo-r16    CommonLocationInfo-r16          OPTIONAL,
    bt-LocationInfo-r16       LogMeasResultListBT-r16         OPTIONAL,
    wlan-LocationInfo-r16     LogMeasResultListWLAN-r16       OPTIONAL,
    sensor-LocationInfo-r16   Sensor-LocationInfo-r16         OPTIONAL,
    ...
}
