NTN-Parameters-r17 ::= SEQUENCE {
    inactiveStateNTN-r17                ENUMERATED {supported}                                OPTIONAL,
    ra-SDT-NTN-r17                      ENUMERATED {supported}                                OPTIONAL,
    srb-SDT-NTN-r17                     ENUMERATED {supported}                                OPTIONAL,
    measAndMobParametersNTN-r17         MeasAndMobParameters                                  OPTIONAL,
    mac-ParametersNTN-r17               MAC-Parameters                                        OPTIONAL,
    phy-ParametersNTN-r17               Phy-Parameters                                        OPTIONAL,
    fdd-Add-UE-NR-CapabilitiesNTN-r17   UE-NR-CapabilityAddXDD-Mode                           OPTIONAL,
    fr1-Add-UE-NR-CapabilitiesNTN-r17   UE-NR-CapabilityAddFRX-Mode                           OPTIONAL,
    ue-BasedPerfMeas-ParametersNTN-r17  UE-BasedPerfMeas-Parameters-r16                       OPTIONAL,
    son-ParametersNTN-r17               SON-Parameters-r16                                    OPTIONAL
}
